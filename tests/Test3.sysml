package FlashlightStarterModel {
            part flashlight {
                exhibit state flashlightStates {
                    state off;
                    transition start then off;
                }
        }
}
